// Glboba defs for the 3 ulps


string cfg_LIBS = "Eagle.To.KiCad.Libs.LIBS";
string cfg_conflictPartsLibsListsize = "Eagle.To.KiCad.Libs.conflictPartsLibsListsize";
string cfg_addLibPrifix = "Eagle.To.KiCad.Libs.addLibPrifix";
string cfg_SCRIP_ULP = "Eagle.To.KiCad.Libs.SCRIP_ULP";
string cfg_TARGET_DIR = "Eagle.To.KiCad.Libs.TARGET_DIR";
string cfg_F0 = "Eagle.To.KiCad.Libs.SCHf0.REF.SCALING";
string cfg_F1 = "Eagle.To.KiCad.Libs.SCHf1.VALUE.SCALING";
string cfg_F2 = "Eagle.To.KiCad.Libs.SCHf2.NAME.SCALING";
string cfg_EnableNetLableFix = "Eagle.To.KiCad.Libs.SCH.NET.LABLE.FIX";
